-- (c) 2014 Eneo Tecnologia <jjprieto@eneotecnologia.com>, <jjprieto@redborder.net>

REDBORDER-MIB DEFINITIONS ::= BEGIN

IMPORTS
	OBJECT-TYPE, NOTIFICATION-TYPE, MODULE-IDENTITY,
	Integer32, Opaque, enterprises, Counter32
	FROM SNMPv2-SMI

	TEXTUAL-CONVENTION, DisplayString, TruthValue
	FROM SNMPv2-TC;

redborder MODULE-IDENTITY
	LAST-UPDATED	"201402210000Z"
	ORGANIZATION	"Eneo Tecnologia S.L."
	CONTACT-INFO 
	"Eneo Tecnologia S.L.
	email: info@eneotecnologia.com
	"
	DESCRIPTION
	"First version of this mib"
	::= { enterprises 39483 }

ips OBJECT IDENTIFIER
	::= { redborder 2 }

rbHwStats OBJECT IDENTIFIER
	::= { ips 1 }

rbSnortStats OBJECT IDENTIFIER
	::= { ips 2 }

-- Type Definitions

PositiveInteger ::= INTEGER (1..2147483647)
InstancesGroupString ::= DisplayString (SIZE (0..128))
StatValuePercent ::= INTEGER (0..100000)
StatValue ::= INTEGER (0..2147483647)
StatString ::= DisplayString (SIZE (0..128))
StatTimestamp ::= INTEGER
StatTimeticks ::= TimeTicks
StatInstance ::= INTEGER (1..64)
InstancesGroupID ::= INTEGER (0..2147483647)
InstancesID ::= INTEGER (0..128)
StatState ::= INTEGER {
		invalid (0),
		normal (1)
	}

manufacturer OBJECT-TYPE
	SYNTAX      DisplayString
	MAX-ACCESS  read-only
	STATUS      current
	DESCRIPTION
	        "System manufacturer."
	::= { rbHwStats 1 }

productName OBJECT-TYPE
	SYNTAX      DisplayString
	MAX-ACCESS  read-only
	STATUS      current
	DESCRIPTION
	        "Product name from manufacturer."
	::= { rbHwStats 2 }


-- Table has to be last in a branch to satisfy snmp walk engine implementation

-- Table of Temperature Sensors

rbTempTable OBJECT-TYPE
	SYNTAX SEQUENCE OF RbTempEntry
	ACCESS  not-accessible
	STATUS  mandatory
	DESCRIPTION
		"Temperature Sensors table"
	::= { rbHwStats 3 }

rbTempEntry OBJECT-TYPE
	SYNTAX	RbTempEntry
	ACCESS	not-accessible
	STATUS	mandatory
	DESCRIPTION
		"Temperature Sensors entries"
	INDEX { systemIndex }
	::= { rbTempTable 1 }

RbTempEntry ::= SEQUENCE {
        tempIndex				PositiveInteger,
	tempSensorName				StatString,
	tempSensorValue				StatValue
}

tempIndex OBJECT-TYPE
	SYNTAX  PositiveInteger
	ACCESS  not-accessible
	STATUS  mandatory
	DESCRIPTION
		"Index for temperature sensors."
	::= { rbTempEntry 1 }

tempSensorName OBJECT-TYPE
	SYNTAX  StatString
	ACCESS  read-only
	STATUS  mandatory
	DESCRIPTION
		"Name of temperature sensor."
	::= { rbTempEntry 2 }

tempSensorValue OBJECT-TYPE
	SYNTAX  StatValue
	UNITS	"degrees C"
	ACCESS  read-only
	STATUS  mandatory
	DESCRIPTION
		"Value of temperature sensor."
	::= { rbTempEntry 3 }

-- Table of FAN sensors

rbFanTable OBJECT-TYPE
	SYNTAX SEQUENCE OF RbFanEntry
	ACCESS  not-accessible
	STATUS  mandatory
	DESCRIPTION
		"FAN Sensors table"
	::= { rbHwStats 4 }

rbFanEntry OBJECT-TYPE
	SYNTAX	RbFanEntry
	ACCESS	not-accessible
	STATUS	mandatory
	DESCRIPTION
		"FAN Sensors entries"
	INDEX { fanIndex }
	::= { rbFanTable 1 }

RbFanEntry ::= SEQUENCE {
     fanIndex				PositiveInteger,
	fanSensorName				StatString,
	fanSensorValue				StatValue
}

fanIndex OBJECT-TYPE
	SYNTAX  PositiveInteger
	ACCESS  not-accessible
	STATUS  mandatory
	DESCRIPTION
		"Index for FAN sensors."
	::= { rbFanEntry 1 }

fanSensorName OBJECT-TYPE
	SYNTAX  StatString
	ACCESS  read-only
	STATUS  mandatory
	DESCRIPTION
		"Name of FAN sensor."
	::= { rbFanEntry 2 }

fanSensorValue OBJECT-TYPE
	SYNTAX  StatValue
	UNITS	"rpm"
	ACCESS  read-only
	STATUS  mandatory
	DESCRIPTION
		"Value of FAN sensor."
	::= { rbFanEntry 3 }



-- Table of snort perfmonitor statistics for every snort process
-- indexed by instances group and instance (snort process)

rbSnortStatsTable OBJECT-TYPE
	SYNTAX SEQUENCE OF RbSnortStatsEntry
	ACCESS	not-accessible
	STATUS	mandatory
	DESCRIPTION
		"Statistics table"
	::= { rbSnortStats 1 }

rbSnortStatsEntry OBJECT-TYPE
	SYNTAX	RbSnortStatsEntry
	ACCESS	not-accessible
	STATUS	mandatory
	DESCRIPTION
		"Statistics entries"
	INDEX { instancesGroupIndex,
		instanceIndex }
	::= { rbSnortStatsTable 1 }

RbSnortStatsEntry ::= SEQUENCE {
	instancesGroupIndex			PositiveInteger,
	instanceIndex				PositiveInteger,
	instancesGroupName			InstancesGroupString,
	instancesGroupID			InstancesGroupID,
	instanceID				InstancesID,
	statState				StatState,
	statTimestamp				StatTimestamp,
	statTimesticks				StatTimeticks,
        alertsPerSecond				StatValue,
        attributeTableReloads			StatValue,
        avgBytesPerIpfragPacket			StatValue,
        avgBytesPerIpreassPacket		StatValue,
        avgBytesPerMplsPacket			StatValue,
        avgBytesPerPacket			StatValue,
        avgBytesPerRebuiltPacket		StatValue,
        avgBytesPerWirePacket			StatValue,
        cpuUsagePercent				StatValue,
        currentAttributeHosts			StatValue,
        currentFrags				StatValue,
        currTcpSessionsClosing			StatValue,
        currTcpSessionsEstablished		StatValue,
        currTcpSessionsInitializing		StatValue,
        deletedSessionsPerSecond		StatValue,
        deletedUdpSessionsPerSecond		StatValue,
        frag3MemInUse				StatValue,
        fragAutofreesPerSecond			StatValue,
        fragCompletesPerSecond			StatValue,
        fragCreatesPerSecond			StatValue,
        fragDeletesPerSecond			StatValue,
        fragFaults				StatValue,
        fragFlushesPerSecond			StatValue,
        fragInsertsPerSecond			StatValue,
        fragTimeouts				StatValue,
        icmp4Echo				StatValue,
        icmp6Echo				StatValue,
        ip4Df					StatValue,
        ip4Opts					StatValue,
        ip4Rf					StatValue,
        ip4Tos					StatValue,
        ip4Trim					StatValue,
        ip4Ttl					StatValue,
        ip6Opts					StatValue,
        ip6Ttl					StatValue,
        ipfragMbitsPerSec			StatValue,
        ipreassMbitsPerSec			StatValue,
        kpacketsIpfragPerSec			StatValue,
        kpacketsIpreassPerSec			StatValue,
        kpacketsPerSecMpls			StatValue,
        kpacketsPerSec				StatValue,
        kpacketsRebuiltPerSec			StatValue,
        kpacketsWirePerSec			StatValue,
        maxFrags				StatValue,
        maxSessions				StatValue,
        maxTcpSessionsInterval			StatValue,
        maxUdpSessions				StatValue,
        mbitsPerSec				StatValue,
        mplsMbitsPerSec				StatValue,
        newSessionsPerSecond			StatValue,
        newUdpSessionsPerSecond			StatValue,
        patmatchPercent				StatValue,
        pktDropPercent				StatValue,
        pktStatsPktsDrop			StatValue,
        pktStatsPktsRecv			StatValue,
        rebuiltMbitsPerSec			StatValue,
        stream5MemInUse				StatValue,
        streamFaults				StatValue,
        streamFlushesPerSecond			StatValue,
        streamTimeouts				StatValue,
        synacksPerSecond			StatValue,
        synsPerSecond				StatValue,
        tcpBlock				StatValue,
        tcpEcnPkt				StatValue,
        tcpEcnSsn				StatValue,
        tcpIpsData				StatValue,
        tcpNs					StatValue,
        tcpOpt					StatValue,
        tcpPad					StatValue,
        tcpRsv					StatValue,
        tcpSessionsClosedPerSecond		StatValue,
        tcpSessionsDroppedAsyncPerSecond	StatValue,
        tcpSessionsMidstreamPerSecond		StatValue,
        tcpSessionsPrunedPerSecond		StatValue,
        tcpSessionsTimedoutPerSecond		StatValue,
        tcpSynOpt				StatValue,
        tcpTrim					StatValue,
        tcpTsEcr				StatValue,
        tcpTsNop				StatValue,
        tcpUrg					StatValue,
        tcpUrp					StatValue,
        totalAlertsPerSecond			StatValue,
        totalBlockedVerdicts			StatValue,
        totalInjectedPackets			StatValue,
        totalSessions				StatValue,
        totalTcpFilteredPackets			StatValue,
        totalUdpFilteredPackets			StatValue,
        totalUdpSessions			StatValue,
        wireMbitsPerSec				StatValue,
        synsSynAcksRatio			StatValue,
        alertsPerMinute				StatValue
}

instancesGroupIndex OBJECT-TYPE
	SYNTAX  PositiveInteger
	ACCESS  not-accessible
	STATUS  mandatory
	DESCRIPTION
		"Index for Instances Groups."
	::= { rbSnortStatsEntry 1 }

instanceIndex OBJECT-TYPE
	SYNTAX  PositiveInteger
	ACCESS  not-accessible
	STATUS  mandatory
	DESCRIPTION
		"Index for Instance."
	::= { rbSnortStatsEntry 2 }

instancesGroupName OBJECT-TYPE
	SYNTAX  InstancesGroupString
        ACCESS  read-only
        STATUS  mandatory
        DESCRIPTION
                "The Instances Group name."
        ::= { rbSnortStatsEntry 3 }

instancesGroupID OBJECT-TYPE
	SYNTAX  InstancesGroupID
        ACCESS  read-only
        STATUS  mandatory
        DESCRIPTION
                "The Instances Group ID."
        ::= { rbSnortStatsEntry 4 }

instanceID OBJECT-TYPE
	SYNTAX  InstancesGroupID
        ACCESS  read-only
        STATUS  mandatory
        DESCRIPTION
                "The Instance ID."
        ::= { rbSnortStatsEntry 5 }


statState OBJECT-TYPE
	SYNTAX	StatState
	ACCESS	read-only
	STATUS	mandatory
	DESCRIPTION
		"The statistic state."
	::= { rbSnortStatsEntry 6 }

statTimestamp OBJECT-TYPE
	SYNTAX	StatTimestamp
	ACCESS	read-only
	STATUS	mandatory
	DESCRIPTION
		"The statistic timestamp. This is the time, in Unix time Epoch, of the obtained value."
	::= { rbSnortStatsEntry 7 }

statTimeticks OBJECT-TYPE
	SYNTAX	StatTimesticks
	ACCESS	read-only
	STATUS	mandatory
	DESCRIPTION
		"The statistic timesticks. Time since last obtained value."
	::= { rbSnortStatsEntry 8 }

alertsPerSecond OBJECT-TYPE
        SYNTAX  StatValue
        UNITS   "(1/1000) alerts/s"
        ACCESS  read-only
        STATUS  mandatory
        DESCRIPTION
                "StatValue 9, alertsPerSecond => alerts_per_second value * 1000 in integer format."
        ::= { rbSnortStatsEntry 9 }

attributeTableReloads OBJECT-TYPE
        SYNTAX  StatValue
        UNITS   "(1/1000) reloads"
        ACCESS  read-only
        STATUS  mandatory
        DESCRIPTION
                "StatValue 10, attributeTableReloads => attribute_table_reloads value * 1000 in integer format."
        ::= { rbSnortStatsEntry 10 }

avgBytesPerIpfragPacket OBJECT-TYPE
        SYNTAX  StatValue
        UNITS   "(1/1000) bytes/pkt"
        ACCESS  read-only
        STATUS  mandatory
        DESCRIPTION
                "StatValue 11, avgBytesPerIpfragPacket => avg_bytes_per_ipfrag_packet value * 1000 in integer format."
        ::= { rbSnortStatsEntry 11 }

avgBytesPerIpreassPacket OBJECT-TYPE
        SYNTAX  StatValue
        UNITS   "(1/1000) bytes/pkt"
        ACCESS  read-only
        STATUS  mandatory
        DESCRIPTION
                "StatValue 12, avgBytesPerIpreassPacket => avg_bytes_per_ipreass_packet value * 1000 in integer format."
        ::= { rbSnortStatsEntry 12 }

avgBytesPerMplsPacket OBJECT-TYPE
        SYNTAX  StatValue
        UNITS   "(1/1000) bytes/pkt"
        ACCESS  read-only
        STATUS  mandatory
        DESCRIPTION
                "StatValue 13, avgBytesPerMplsPacket => avg_bytes_per_mpls_packet value * 1000 in integer format."
        ::= { rbSnortStatsEntry 13 }

avgBytesPerPacket OBJECT-TYPE
        SYNTAX  StatValue
        UNITS   "(1/1000) bytes/pkt"
        ACCESS  read-only
        STATUS  mandatory
        DESCRIPTION
                "StatValue 14, avgBytesPerPacket => avg_bytes_per_packet value * 1000 in integer format."
        ::= { rbSnortStatsEntry 14 }

avgBytesPerRebuiltPacket OBJECT-TYPE
        SYNTAX  StatValue
        UNITS   "(1/1000) bytes/pkt"
        ACCESS  read-only
        STATUS  mandatory
        DESCRIPTION
                "StatValue 15, avgBytesPerRebuiltPacket => avg_bytes_per_rebuilt_packet value * 1000 in integer format."
        ::= { rbSnortStatsEntry 15 }

avgBytesPerWirePacket OBJECT-TYPE
        SYNTAX  StatValue
        UNITS   "(1/1000) bytes/pkt"
        ACCESS  read-only
        STATUS  mandatory
        DESCRIPTION
                "StatValue 16, avgBytesPerWirePacket => avg_bytes_per_wire_packet value * 1000 in integer format."
        ::= { rbSnortStatsEntry 16 }

cpuUsagePercent OBJECT-TYPE
        SYNTAX  StatValue
        UNITS   "(1/1000) %"
        ACCESS  read-only
        STATUS  mandatory
        DESCRIPTION
                "StatValue 17, cpuUsagePercent => cpu_usage_percent value * 1000 in integer format."
        ::= { rbSnortStatsEntry 17 }

currentAttributeHosts OBJECT-TYPE
        SYNTAX  StatValue
        ACCESS  read-only
        STATUS  mandatory
        DESCRIPTION
                "StatValue 18, currentAttributeHosts => current_attribute_hosts value * 1000 in integer format."
        ::= { rbSnortStatsEntry 18 }

currentFrags OBJECT-TYPE
        SYNTAX  StatValue
        UNITS   "(1/1000) frags"
        ACCESS  read-only
        STATUS  mandatory
        DESCRIPTION
                "StatValue 19, currentFrags => current_frags value * 1000 in integer format."
        ::= { rbSnortStatsEntry 19 }

currTcpSessionsClosing OBJECT-TYPE
        SYNTAX  StatValue
        UNITS   "(1/1000) sessions"
        ACCESS  read-only
        STATUS  mandatory
        DESCRIPTION
                "StatValue 20, currTcpSessionsClosing => curr_tcp_sessions_closing value * 1000 in integer format."
        ::= { rbSnortStatsEntry 20 }

currTcpSessionsEstablished OBJECT-TYPE
        SYNTAX  StatValue
        UNITS   "(1/1000) sessions"
        ACCESS  read-only
        STATUS  mandatory
        DESCRIPTION
                "StatValue 21, currTcpSessionsEstablished => curr_tcp_sessions_established value * 1000 in integer format."
        ::= { rbSnortStatsEntry 21 }

currTcpSessionsInitializing OBJECT-TYPE
        SYNTAX  StatValue
        UNITS   "(1/1000) sessions"
        ACCESS  read-only
        STATUS  mandatory
        DESCRIPTION
                "StatValue 22, currTcpSessionsInitializing => curr_tcp_sessions_initializing value * 1000 in integer format."
        ::= { rbSnortStatsEntry 22 }

deletedSessionsPerSecond OBJECT-TYPE
        SYNTAX  StatValue
        UNITS   "(1/1000) sessions/s"
        ACCESS  read-only
        STATUS  mandatory
        DESCRIPTION
                "StatValue 23, deletedSessionsPerSecond => deleted_sessions_per_second value * 1000 in integer format."
        ::= { rbSnortStatsEntry 23 }

deletedUdpSessionsPerSecond OBJECT-TYPE
        SYNTAX  StatValue
        UNITS   "(1/1000) sessions/s"
        ACCESS  read-only
        STATUS  mandatory
        DESCRIPTION
                "StatValue 24, deletedUdpSessionsPerSecond => deleted_udp_sessions_per_second value * 1000 in integer format."
        ::= { rbSnortStatsEntry 24 }

frag3MemInUse OBJECT-TYPE
        SYNTAX  StatValue
        UNITS   "(1/1000) bytes"
        ACCESS  read-only
        STATUS  mandatory
        DESCRIPTION
                "StatValue 25, frag3MemInUse => frag3_mem_in_use value * 1000 in integer format."
        ::= { rbSnortStatsEntry 25 }

fragAutofreesPerSecond OBJECT-TYPE
        SYNTAX  StatValue
        UNITS   "(1/1000) frees/s"
        ACCESS  read-only
        STATUS  mandatory
        DESCRIPTION
                "StatValue 26, fragAutofreesPerSecond => frag_autofrees_per_second value * 1000 in integer format."
        ::= { rbSnortStatsEntry 26 }

fragCompletesPerSecond OBJECT-TYPE
        SYNTAX  StatValue
        UNITS   "(1/1000) completes/s"
        ACCESS  read-only
        STATUS  mandatory
        DESCRIPTION
                "StatValue 27, fragCompletesPerSecond => frag_completes_per_second value * 1000 in integer format."
        ::= { rbSnortStatsEntry 27 }

fragCreatesPerSecond OBJECT-TYPE
        SYNTAX  StatValue
        UNITS   "(1/1000) creates/s"
        ACCESS  read-only
        STATUS  mandatory
        DESCRIPTION
                "StatValue 28, fragCreatesPerSecond => frag_creates_per_second value * 1000 in integer format."
        ::= { rbSnortStatsEntry 28 }

fragDeletesPerSecond OBJECT-TYPE
        SYNTAX  StatValue
        UNITS   "(1/1000) deletes/s"
        ACCESS  read-only
        STATUS  mandatory
        DESCRIPTION
                "StatValue 29, fragDeletesPerSecond => frag_deletes_per_second value * 1000 in integer format."
        ::= { rbSnortStatsEntry 29 }

fragFaults OBJECT-TYPE
        SYNTAX  StatValue
        UNITS   "(1/1000) faults"
        ACCESS  read-only
        STATUS  mandatory
        DESCRIPTION
                "StatValue 30, fragFaults => frag_faults value * 1000 in integer format."
        ::= { rbSnortStatsEntry 30 }

fragFlushesPerSecond OBJECT-TYPE
        SYNTAX  StatValue
        UNITS   "(1/1000) flush/s"
        ACCESS  read-only
        STATUS  mandatory
        DESCRIPTION
                "StatValue 31, fragFlushesPerSecond => frag_flushes_per_second value * 1000 in integer format."
        ::= { rbSnortStatsEntry 31 }

fragInsertsPerSecond OBJECT-TYPE
        SYNTAX  StatValue
        UNITS   "(1/1000) inserts/s"
        ACCESS  read-only
        STATUS  mandatory
        DESCRIPTION
                "StatValue 32, fragInsertsPerSecond => frag_inserts_per_second value * 1000 in integer format."
        ::= { rbSnortStatsEntry 32 }

fragTimeouts OBJECT-TYPE
        SYNTAX  StatValue
        UNITS   "(1/1000) timeouts"
        ACCESS  read-only
        STATUS  mandatory
        DESCRIPTION
                "StatValue 33, fragTimeouts => frag_timeouts value * 1000 in integer format."
        ::= { rbSnortStatsEntry 33 }

icmp4Echo OBJECT-TYPE
        SYNTAX  StatValue
        UNITS   "(1/1000) pkts"
        ACCESS  read-only
        STATUS  mandatory
        DESCRIPTION
                "StatValue 34, icmp4Echo => icmp4::echo value * 1000 in integer format."
        ::= { rbSnortStatsEntry 34 }

icmp6Echo OBJECT-TYPE
        SYNTAX  StatValue
        UNITS   "(1/1000) pkts"
        ACCESS  read-only
        STATUS  mandatory
        DESCRIPTION
                "StatValue 35, icmp6Echo => icmp6::echo value * 1000 in integer format."
        ::= { rbSnortStatsEntry 35 }

ip4Df OBJECT-TYPE
        SYNTAX  StatValue
        UNITS   "(1/1000) pkts"
        ACCESS  read-only
        STATUS  mandatory
        DESCRIPTION
                "StatValue 36, ip4Df => ip4::df value * 1000 in integer format."
        ::= { rbSnortStatsEntry 36 }

ip4Opts OBJECT-TYPE
        SYNTAX  StatValue
        UNITS   "(1/1000) pkts"
        ACCESS  read-only
        STATUS  mandatory
        DESCRIPTION
                "StatValue 37, ip4Opts => ip4::opts value * 1000 in integer format."
        ::= { rbSnortStatsEntry 37 }

ip4Rf OBJECT-TYPE
        SYNTAX  StatValue
        UNITS   "(1/1000) pkts"
        ACCESS  read-only
        STATUS  mandatory
        DESCRIPTION
                "StatValue 38, ip4Rf => ip4::rf value * 1000 in integer format."
        ::= { rbSnortStatsEntry 38 }

ip4Tos OBJECT-TYPE
        SYNTAX  StatValue
        UNITS   "(1/1000) pkts"
        ACCESS  read-only
        STATUS  mandatory
        DESCRIPTION
                "StatValue 39, ip4Tos => ip4::tos value * 1000 in integer format."
        ::= { rbSnortStatsEntry 39 }

ip4Trim OBJECT-TYPE
        SYNTAX  StatValue
        UNITS   "(1/1000) pkts"
        ACCESS  read-only
        STATUS  mandatory
        DESCRIPTION
                "StatValue 40, ip4Trim => ip4::trim value * 1000 in integer format."
        ::= { rbSnortStatsEntry 40 }

ip4Ttl OBJECT-TYPE
        SYNTAX  StatValue
        UNITS   "(1/1000) seconds"
        ACCESS  read-only
        STATUS  mandatory
        DESCRIPTION
                "StatValue 41, ip4Ttl => ip4::ttl value * 1000 in integer format."
        ::= { rbSnortStatsEntry 41 }

ip6Opts OBJECT-TYPE
        SYNTAX  StatValue
        UNITS   "(1/1000) pkts"
        ACCESS  read-only
        STATUS  mandatory
        DESCRIPTION
                "StatValue 42, ip6Opts => ip6::opts value * 1000 in integer format."
        ::= { rbSnortStatsEntry 42 }

ip6Ttl OBJECT-TYPE
        SYNTAX  StatValue
        UNITS   "(1/1000) seconds"
        ACCESS  read-only
        STATUS  mandatory
        DESCRIPTION
                "StatValue 43, ip6Ttl => ip6::ttl value * 1000 in integer format."
        ::= { rbSnortStatsEntry 43 }

ipfragMbitsPerSec OBJECT-TYPE
        SYNTAX  StatValue
        UNITS   "(1/1000) Mbits/s"
        ACCESS  read-only
        STATUS  mandatory
        DESCRIPTION
                "StatValue 44, ipfragMbitsPerSec => ipfrag_mbits_per_sec.realtime value * 1000 in integer format."
        ::= { rbSnortStatsEntry 44 }

ipreassMbitsPerSec OBJECT-TYPE
        SYNTAX  StatValue
        UNITS   "(1/1000) Mbits/s"
        ACCESS  read-only
        STATUS  mandatory
        DESCRIPTION
                "StatValue 45, ipreassMbitsPerSec => ipreass_mbits_per_sec.realtime value * 1000 in integer format."
        ::= { rbSnortStatsEntry 45 }

kpacketsIpfragPerSec OBJECT-TYPE
        SYNTAX  StatValue
        UNITS   "(1/1000) kpkts/s"
        ACCESS  read-only
        STATUS  mandatory
        DESCRIPTION
                "StatValue 46, kpacketsIpfragPerSec => kpackets_ipfrag_per_sec.realtime value * 1000 in integer format."
        ::= { rbSnortStatsEntry 46 }

kpacketsIpreassPerSec OBJECT-TYPE
        SYNTAX  StatValue
        UNITS   "(1/1000) kpkts/s"
        ACCESS  read-only
        STATUS  mandatory
        DESCRIPTION
                "StatValue 47, kpacketsIpreassPerSec => kpackets_ipreass_per_sec.realtime value * 1000 in integer format."
        ::= { rbSnortStatsEntry 47 }

kpacketsPerSecMpls OBJECT-TYPE
        SYNTAX  StatValue
        UNITS   "(1/1000) kpkts/s"
        ACCESS  read-only
        STATUS  mandatory
        DESCRIPTION
                "StatValue 48, kpacketsPerSecMpls => kpackets_per_sec_mpls.realtime value * 1000 in integer format."
        ::= { rbSnortStatsEntry 48 }

kpacketsPerSec OBJECT-TYPE
        SYNTAX  StatValue
        UNITS   "(1/1000) kpkts/s"
        ACCESS  read-only
        STATUS  mandatory
        DESCRIPTION
                "StatValue 49, kpacketsPerSec => kpackets_per_sec.realtime value * 1000 in integer format."
        ::= { rbSnortStatsEntry 49 }

kpacketsRebuiltPerSec OBJECT-TYPE
        SYNTAX  StatValue
        UNITS   "(1/1000) kpkts/s"
        ACCESS  read-only
        STATUS  mandatory
        DESCRIPTION
                "StatValue 50, kpacketsRebuiltPerSec => kpackets_rebuilt_per_sec.realtime value * 1000 in integer format."
        ::= { rbSnortStatsEntry 50 }

kpacketsWirePerSec OBJECT-TYPE
        SYNTAX  StatValue
        UNITS   "(1/1000) kpkts/s"
        ACCESS  read-only
        STATUS  mandatory
        DESCRIPTION
                "StatValue 51, kpacketsWirePerSec => kpackets_wire_per_sec.realtime value * 1000 in integer format."
        ::= { rbSnortStatsEntry 51 }

maxFrags OBJECT-TYPE
        SYNTAX  StatValue
        UNITS   "(1/1000) frags"
        ACCESS  read-only
        STATUS  mandatory
        DESCRIPTION
                "StatValue 52, maxFrags => max_frags value * 1000 in integer format."
        ::= { rbSnortStatsEntry 52 }

maxSessions OBJECT-TYPE
        SYNTAX  StatValue
        UNITS   "(1/1000) sessions"
        ACCESS  read-only
        STATUS  mandatory
        DESCRIPTION
                "StatValue 53, maxSessions => max_sessions value * 1000 in integer format."
        ::= { rbSnortStatsEntry 53 }

maxTcpSessionsInterval OBJECT-TYPE
        SYNTAX  StatValue
        UNITS   "(1/1000) sessions"
        ACCESS  read-only
        STATUS  mandatory
        DESCRIPTION
                "StatValue 54, maxTcpSessionsInterval => max_tcp_sessions_interval value * 1000 in integer format."
        ::= { rbSnortStatsEntry 54 }

maxUdpSessions OBJECT-TYPE
        SYNTAX  StatValue
        UNITS   "(1/1000) sessions"
        ACCESS  read-only
        STATUS  mandatory
        DESCRIPTION
                "StatValue 55, maxUdpSessions => max_udp_sessions value * 1000 in integer format."
        ::= { rbSnortStatsEntry 55 }

mbitsPerSec OBJECT-TYPE
        SYNTAX  StatValue
        UNITS   "(1/1000) Mbits/s"
        ACCESS  read-only
        STATUS  mandatory
        DESCRIPTION
                "StatValue 56, mbitsPerSec => mbits_per_sec.realtime value * 1000 in integer format."
        ::= { rbSnortStatsEntry 56 }

mplsMbitsPerSec OBJECT-TYPE
        SYNTAX  StatValue
        UNITS   "(1/1000) Mbits/s"
        ACCESS  read-only
        STATUS  mandatory
        DESCRIPTION
                "StatValue 57, mplsMbitsPerSec => mpls_mbits_per_sec.realtime value * 1000 in integer format."
        ::= { rbSnortStatsEntry 57 }

newSessionsPerSecond OBJECT-TYPE
        SYNTAX  StatValue
        UNITS   "(1/1000) sessions/s"
        ACCESS  read-only
        STATUS  mandatory
        DESCRIPTION
                "StatValue 58, newSessionsPerSecond => new_sessions_per_second value * 1000 in integer format."
        ::= { rbSnortStatsEntry 58 }

newUdpSessionsPerSecond OBJECT-TYPE
        SYNTAX  StatValue
        UNITS   "(1/1000) sessions/s"
        ACCESS  read-only
        STATUS  mandatory
        DESCRIPTION
                "StatValue 59, newUdpSessionsPerSecond => new_udp_sessions_per_second value * 1000 in integer format."
        ::= { rbSnortStatsEntry 59 }

patmatchPercent OBJECT-TYPE
        SYNTAX  StatValue
        UNITS   "(1/1000) %"
        ACCESS  read-only
        STATUS  mandatory
        DESCRIPTION
                "StatValue 60, patmatchPercent => patmatch_percent value * 1000 in integer format."
        ::= { rbSnortStatsEntry 60 }

pktDropPercent OBJECT-TYPE
        SYNTAX  StatValue
        UNITS   "(1/1000) %"
        ACCESS  read-only
        STATUS  mandatory
        DESCRIPTION
                "StatValue 61, pktDropPercent => pkt_drop_percent value * 1000 in integer format."
        ::= { rbSnortStatsEntry 61 }

pktStatsPktsDrop OBJECT-TYPE
        SYNTAX  StatValue
        UNITS   "(1/1000) pkts"
        ACCESS  read-only
        STATUS  mandatory
        DESCRIPTION
                "StatValue 62, pktStatsPktsDrop => pkt_stats.pkts_drop value * 1000 in integer format."
        ::= { rbSnortStatsEntry 62 }

pktStatsPktsRecv OBJECT-TYPE
        SYNTAX  StatValue
        UNITS   "(1/1000) pkts"
        ACCESS  read-only
        STATUS  mandatory
        DESCRIPTION
                "StatValue 63, pktStatsPktsRecv => pkt_stats.pkts_recv value * 1000 in integer format."
        ::= { rbSnortStatsEntry 63 }

rebuiltMbitsPerSec OBJECT-TYPE
        SYNTAX  StatValue
        UNITS   "(1/1000) Mbits/s"
        ACCESS  read-only
        STATUS  mandatory
        DESCRIPTION
                "StatValue 64, rebuiltMbitsPerSec => rebuilt_mbits_per_sec.realtime value * 1000 in integer format."
        ::= { rbSnortStatsEntry 64 }

stream5MemInUse OBJECT-TYPE
        SYNTAX  StatValue
        UNITS   "(1/1000) bytes"
        ACCESS  read-only
        STATUS  mandatory
        DESCRIPTION
                "StatValue 65, stream5MemInUse => stream5_mem_in_use value * 1000 in integer format."
        ::= { rbSnortStatsEntry 65 }

streamFaults OBJECT-TYPE
        SYNTAX  StatValue
        UNITS   "(1/1000) faults"
        ACCESS  read-only
        STATUS  mandatory
        DESCRIPTION
                "StatValue 66, streamFaults => stream_faults value * 1000 in integer format."
        ::= { rbSnortStatsEntry 66 }

streamFlushesPerSecond OBJECT-TYPE
        SYNTAX  StatValue
        UNITS   "(1/1000) flush/s"
        ACCESS  read-only
        STATUS  mandatory
        DESCRIPTION
                "StatValue 67, streamFlushesPerSecond => stream_flushes_per_second value * 1000 in integer format."
        ::= { rbSnortStatsEntry 67 }

streamTimeouts OBJECT-TYPE
        SYNTAX  StatValue
        UNITS   "(1/1000) timeouts"
        ACCESS  read-only
        STATUS  mandatory
        DESCRIPTION
                "StatValue 68, streamTimeouts => stream_timeouts value * 1000 in integer format."
        ::= { rbSnortStatsEntry 68 }

synacksPerSecond OBJECT-TYPE
        SYNTAX  StatValue
        UNITS   "(1/1000) synacks/s"
        ACCESS  read-only
        STATUS  mandatory
        DESCRIPTION
                "StatValue 69, synacksPerSecond => synacks_per_second value * 1000 in integer format."
        ::= { rbSnortStatsEntry 69 }

synsPerSecond OBJECT-TYPE
        SYNTAX  StatValue
        UNITS   "(1/1000) syns/s"
        ACCESS  read-only
        STATUS  mandatory
        DESCRIPTION
                "StatValue 70, synsPerSecond => syns_per_second value * 1000 in integer format."
        ::= { rbSnortStatsEntry 70 }

tcpBlock OBJECT-TYPE
        SYNTAX  StatValue
        ACCESS  read-only
        STATUS  mandatory
        DESCRIPTION
                "StatValue 71, tcpBlock => tcp::block value * 1000 in integer format."
        ::= { rbSnortStatsEntry 71 }

tcpEcnPkt OBJECT-TYPE
        SYNTAX  StatValue
        UNITS   "(1/1000) pkts"
        ACCESS  read-only
        STATUS  mandatory
        DESCRIPTION
                "StatValue 72, tcpEcnPkt => tcp::ecn_pkt value * 1000 in integer format."
        ::= { rbSnortStatsEntry 72 }

tcpEcnSsn OBJECT-TYPE
        SYNTAX  StatValue
        UNITS   "(1/1000) sessions"
        ACCESS  read-only
        STATUS  mandatory
        DESCRIPTION
                "StatValue 73, tcpEcnSsn => tcp::ecn_ssn value * 1000 in integer format."
        ::= { rbSnortStatsEntry 73 }

tcpIpsData OBJECT-TYPE
        SYNTAX  StatValue
        ACCESS  read-only
        STATUS  mandatory
        DESCRIPTION
                "StatValue 74, tcpIpsData => tcp::ips_data value * 1000 in integer format."
        ::= { rbSnortStatsEntry 74 }

tcpNs OBJECT-TYPE
        SYNTAX  StatValue
        ACCESS  read-only
        STATUS  mandatory
        DESCRIPTION
                "StatValue 75, tcpNs => tcp::ns value * 1000 in integer format."
        ::= { rbSnortStatsEntry 75 }

tcpOpt OBJECT-TYPE
        SYNTAX  StatValue
        ACCESS  read-only
        STATUS  mandatory
        DESCRIPTION
                "StatValue 76, tcpOpt => tcp::opt value * 1000 in integer format."
        ::= { rbSnortStatsEntry 76 }

tcpPad OBJECT-TYPE
        SYNTAX  StatValue
        ACCESS  read-only
        STATUS  mandatory
        DESCRIPTION
                "StatValue 77, tcpPad => tcp::pad value * 1000 in integer format."
        ::= { rbSnortStatsEntry 77 }

tcpRsv OBJECT-TYPE
        SYNTAX  StatValue
        ACCESS  read-only
        STATUS  mandatory
        DESCRIPTION
                "StatValue 78, tcpRsv => tcp::rsv value * 1000 in integer format."
        ::= { rbSnortStatsEntry 78 }

tcpSessionsClosedPerSecond OBJECT-TYPE
        SYNTAX  StatValue
        UNITS   "(1/1000) sessions/s"
        ACCESS  read-only
        STATUS  mandatory
        DESCRIPTION
                "StatValue 79, tcpSessionsClosedPerSecond => tcp_sessions_closed_per_second value * 1000 in integer format."
        ::= { rbSnortStatsEntry 79 }

tcpSessionsDroppedAsyncPerSecond OBJECT-TYPE
        SYNTAX  StatValue
        UNITS   "(1/1000) sessions"
        ACCESS  read-only
        STATUS  mandatory
        DESCRIPTION
                "StatValue 80, tcpSessionsDroppedAsyncPerSecond => tcp_sessions_dropped_async_per_second value * 1000 in integer format."
        ::= { rbSnortStatsEntry 80 }

tcpSessionsMidstreamPerSecond OBJECT-TYPE
        SYNTAX  StatValue
        UNITS   "(1/1000) sessions/s"
        ACCESS  read-only
        STATUS  mandatory
        DESCRIPTION
                "StatValue 81, tcpSessionsMidstreamPerSecond => tcp_sessions_midstream_per_second value * 1000 in integer format."
        ::= { rbSnortStatsEntry 81 }

tcpSessionsPrunedPerSecond OBJECT-TYPE
        SYNTAX  StatValue
        UNITS   "(1/1000) sessions/s"
        ACCESS  read-only
        STATUS  mandatory
        DESCRIPTION
                "StatValue 82, tcpSessionsPrunedPerSecond => tcp_sessions_pruned_per_second value * 1000 in integer format."
        ::= { rbSnortStatsEntry 82 }

tcpSessionsTimedoutPerSecond OBJECT-TYPE
        SYNTAX  StatValue
        UNITS   "(1/1000) sessions/s"
        ACCESS  read-only
        STATUS  mandatory
        DESCRIPTION
                "StatValue 83, tcpSessionsTimedoutPerSecond => tcp_sessions_timedout_per_second value * 1000 in integer format."
        ::= { rbSnortStatsEntry 83 }

tcpSynOpt OBJECT-TYPE
        SYNTAX  StatValue
        ACCESS  read-only
        STATUS  mandatory
        DESCRIPTION
                "StatValue 84, tcpSynOpt => tcp::syn_opt value * 1000 in integer format."
        ::= { rbSnortStatsEntry 84 }

tcpTrim OBJECT-TYPE
        SYNTAX  StatValue
        ACCESS  read-only
        STATUS  mandatory
        DESCRIPTION
                "StatValue 85, tcpTrim => tcp::trim value * 1000 in integer format."
        ::= { rbSnortStatsEntry 85 }

tcpTsEcr OBJECT-TYPE
        SYNTAX  StatValue
        ACCESS  read-only
        STATUS  mandatory
        DESCRIPTION
                "StatValue 86, tcpTsEcr => tcp::ts_ecr value * 1000 in integer format."
        ::= { rbSnortStatsEntry 86 }

tcpTsNop OBJECT-TYPE
        SYNTAX  StatValue
        ACCESS  read-only
        STATUS  mandatory
        DESCRIPTION
                "StatValue 87, tcpTsNop => tcp::ts_nop value * 1000 in integer format."
        ::= { rbSnortStatsEntry 87 }

tcpUrg OBJECT-TYPE
        SYNTAX  StatValue
        ACCESS  read-only
        STATUS  mandatory
        DESCRIPTION
                "StatValue 88, tcpUrg => tcp::urg value * 1000 in integer format."
        ::= { rbSnortStatsEntry 88 }

tcpUrp OBJECT-TYPE
        SYNTAX  StatValue
        ACCESS  read-only
        STATUS  mandatory
        DESCRIPTION
                "StatValue 89, tcpUrp => tcp::urp value * 1000 in integer format."
        ::= { rbSnortStatsEntry 89 }

totalAlertsPerSecond OBJECT-TYPE
        SYNTAX  StatValue
        UNITS   "(1/1000) alerts/s"
        ACCESS  read-only
        STATUS  mandatory
        DESCRIPTION
                "StatValue 90, totalAlertsPerSecond => total_alerts_per_second value * 1000 in integer format."
        ::= { rbSnortStatsEntry 90 }

totalBlockedVerdicts OBJECT-TYPE
        SYNTAX  StatValue
        UNITS   "(1/1000) pkts"
        ACCESS  read-only
        STATUS  mandatory
        DESCRIPTION
                "StatValue 91, totalBlockedVerdicts => total_blocked_verdicts value * 1000 in integer format."
        ::= { rbSnortStatsEntry 91 }

totalInjectedPackets OBJECT-TYPE
        SYNTAX  StatValue
        UNITS   "(1/1000) pkts"
        ACCESS  read-only
        STATUS  mandatory
        DESCRIPTION
                "StatValue 92, totalInjectedPackets => total_injected_packets value * 1000 in integer format."
        ::= { rbSnortStatsEntry 92 }

totalSessions OBJECT-TYPE
        SYNTAX  StatValue
        UNITS   "(1/1000) sessions"
        ACCESS  read-only
        STATUS  mandatory
        DESCRIPTION
                "StatValue 93, totalSessions => total_sessions value * 1000 in integer format."
        ::= { rbSnortStatsEntry 93 }

totalTcpFilteredPackets OBJECT-TYPE
        SYNTAX  StatValue
        UNITS   "(1/1000) pkts"
        ACCESS  read-only
        STATUS  mandatory
        DESCRIPTION
                "StatValue 94, totalTcpFilteredPackets => total_tcp_filtered_packets value * 1000 in integer format."
        ::= { rbSnortStatsEntry 94 }

totalUdpFilteredPackets OBJECT-TYPE
        SYNTAX  StatValue
        UNITS   "(1/1000) pkts"
        ACCESS  read-only
        STATUS  mandatory
        DESCRIPTION
                "StatValue 95, totalUdpFilteredPackets => total_udp_filtered_packets value * 1000 in integer format."
        ::= { rbSnortStatsEntry 95 }

totalUdpSessions OBJECT-TYPE
        SYNTAX  StatValue
        UNITS   "(1/1000) sessions"
        ACCESS  read-only
        STATUS  mandatory
        DESCRIPTION
                "StatValue 96, totalUdpSessions => total_udp_sessions value * 1000 in integer format."
        ::= { rbSnortStatsEntry 96 }

wireMbitsPerSec OBJECT-TYPE
        SYNTAX  StatValue
        UNITS   "(1/1000) Mbits/s"
        ACCESS  read-only
        STATUS  mandatory
        DESCRIPTION
                "StatValue 97, wireMbitsPerSec => wire_mbits_per_sec.realtime value * 1000 in integer format."
        ::= { rbSnortStatsEntry 97 }

synsSynAcksRatio OBJECT-TYPE
        SYNTAX  StatValue
        UNITS   "(1/1000) syns/synacks"
        ACCESS  read-only
        STATUS  mandatory
        DESCRIPTION
                "StatValue 98, synsSynAcksRatio => syns_synacks_ratio value * 1000 in integer format."
        ::= { rbSnortStatsEntry 98 }

alertsPerMinute OBJECT-TYPE
        SYNTAX  StatValue
        UNITS   "(1/1000) alerts/min"
        ACCESS  read-only
        STATUS  mandatory
        DESCRIPTION
                "StatValue 99, alertsPerMinute => alerts_per_minute value * 1000 in integer format."
        ::= { rbSnortStatsEntry 99 }


END
